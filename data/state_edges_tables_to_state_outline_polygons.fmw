FME workspace state_edges_tables_to_state_outline_polygons.fmw

Parameters:
- SourceDataset_ORACLE8I = EDEVBNCH.GEO.CENSUS.GOV   # Source Oracle Spatial Object Service
- FEATURE_TYPES = DADSGEN.STATE_EDGES_Z6
- DestDataset_SHAPE = Q:\gz\dev\devbnch\mcard001\qa_20120911   # Destination ESRI Shape Directory

Readers:
- ORACLE8I_1: ORACLE8I from $(SourceDataset_ORACLE8I)

Writers:
- SHAPE_1: SHAPE to $(DestDataset_SHAPE)

STATE_EDGES_Z6_LINE (reader ORACLE8I_1)
    attributes: SRC varchar2(8), TYPE varchar2(32), L_STATEFP varchar2(32), R_STATEFP varchar2(32), STEDGE_ID float
    -> TopologyBuilder [input 2]
TopologyBuilder
    MAX = 0
    ALL_EDGES = Yes
    CLEAN_DATA = No
    PROP_ATTRS = Yes
    ALLOW_CYCLES = Yes
    OVERLAPPING_MODE = No
    LINE -> PolygonBuilder
PolygonBuilder
    GROUP_BY = _polygons
    LIST_NAME = list
    ALLOW_CYCLES = Yes
    POLYGON -> AttributeCreator
AttributeCreator
    ATTR_LIST = statefp,"",filename,state_outline_
    -> AttributeCopier
AttributeCopier
    ATTR_LIST = statefp,list{0}.L_STATEFP,statefp,list{0}.R_STATEFP
    -> AttributeCreator_2
AttributeCreator_2
    ATTR_LIST = final_filename,fme_basicstring:16%15:@Value(filename)@Value(statefp)
    -> Reprojector
Reprojector
    DEST = SPHERICAL_MERCATOR
    SOURCE = Read from feature
    RASTER_CELL_SIZE = Preserve Cells
    INTERPOLATION_TYPE_NAME = Nearest Neighbor
    STROKE_ARCS = Yes
    REPROJECTED -> state_outline (writer SHAPE_1)
state_outline (writer SHAPE_1)

FME custom transformer AttributePacker
This transformer packs all the attributes that fit the user filter into a single attribute, in the form name:value:name:value... This is useful for storing multiple format attributes in a single database field for future use.
The transformer takes two parameters:
Filter Prefix: All attributes with this prefix will be added to the packed attribute. Leaving this value blank will pack all the attributes.
Packed Attribute Name: The name of the new attribute containing the packed values
Copyright (c) 2012 Safe Software Inc.
Permission is granted to anyone, free of charge, to use, modify and distribute the object code form of this template for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- FILTER =   # Filter Prefix (blank for all attributes)
- PACKED = _packed   # Packed Attribute Name

INPUT (input)
    -> ParameterFetcher
Note: Get filter value
ParameterFetcher
    ATTR_LIST = AP_FILTER {$(FILTER)} AP_PACKED {$(PACKED)}
    -> PythonCaller
Note: import fmeobjects / # This class will create a packed list of format / # attributes suitable for use with @SupplyAttributes() / def packIgdsAtts(feature): / # get a list of attribute names / attlist = feature.getAllAttributeNames() / # get filter value / filter = feature.getAttribute('AP_FILTER') / # get packed attribute name / packedAtt = feature.getAttribute('AP_PACKED') / # create list for packed attributes / packed = [] / # loop through attribute names / for att in attlist: / # extract only igds format attributes / if filter in att and att!='AP_FILTER' and att!='AP_PACKED' : / # append attribute name / packed.append(att) / # append attribute value / packed.append(str(feature.getAttribute(att))) / # add packed attribute in the form name:value:name:value:name:value... / feature.setAttribute(packedAtt,':'.join(packed))
PythonCaller
    NEW_ATTRIBUTES = $(PACKED)
    PYTHONSYMBOL = packIgdsAtts
    PYTHONSOURCE:
      import fmeobjects

      # This class will create a packed list of format
      # attributes suitable for use with @SupplyAttributes()

      def packIgdsAtts(feature):

         # get a list of attribute names
         attlist = feature.getAllAttributeNames()

         # get filter value
         filter = feature.getAttribute('AP_FILTER')

         # get packed attribute name
         packedAtt = feature.getAttribute('AP_PACKED')

         # create list for packed attributes
         packed = []

         # loop through attribute names
         for att in attlist:
             # extract only igds format attributes
             if filter in att and att!='AP_FILTER' and att!='AP_PACKED' :
                 # append attribute name
                 packed.append(att)
                 # append attribute value
                 packed.append(str(feature.getAttribute(att)))

         # add packed attribute in the form name:value:name:value:name:value...
         feature.setAttribute(packedAtt,':'.join(packed))
    -> AttributeRemover
Note: Remove temporary attributes
AttributeRemover
    REMOVE_ATTRS = AP_FILTER,AP_PACKED
    -> OUTPUT (output)
OUTPUT (output)
Dissolver
    DISSOLVE_MODE = Traditional
    ACCUM_INPUT_ATTRS = No
    OVRLP = No Overlap
AttributeCopier
