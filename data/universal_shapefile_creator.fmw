FME workspace universal_shapefile_creator.fmw

Parameters:
- SourceDataset =   # Source Oracle Spatial Object Service
- DestDataset =   # Destination Esri Shape Directory
- ShapeName =
- USER_NAME =   # Username
- PASSWORD =   # PASSWORD Password
- ORACLE8I_IN_WHERE_CLAUSE_ORACLE82 =   # WHERE Clause
- SchemaName =
- TableName =
- LOG_FILE =   # Log File
- Projection =
- SchemaTable = $(SchemaName).$(TableName)

Readers:
- ORACLE8I_1: ORACLE8I from $(SourceDataset)

Writers:
- SHAPE_1: SHAPE to $(DestDataset)

Z899TM_FSL010V (reader ORACLE8I_1)
    attributes: GEO_ID varchar2(60), NAME varchar2(90), LSAD varchar2(7)
    -> Reprojector
Reprojector
    DEST = $(Projection)
    RASTER_CELL_SIZE = Preserve Cells
    STROKE_ARCS = Yes
    SOURCE = Read from feature
    INTERPOLATION_TYPE_NAME = Nearest Neighbor
    REPROJECTED -> GeometryValidator
GeometryValidator
    DUP_COORDS_CHECK_Z = Yes
    PRESETS = OGC
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = No
    ISSUE_ATTR_NAME = _issues
    OGC_SIMPLE_CHECK = OGC_SIMPLE_CHECK
    PLANAR_TOLERANCE_MODE = Auto
    OGC_VALID_CHECK = OGC_VALID_CHECK
    PASSED -> DYNAMIC (writer SHAPE_1)
    FAILED -> DYNAMIC00 (writer SHAPE_1)
DYNAMIC (writer SHAPE_1)
DYNAMIC00 (writer SHAPE_1)
