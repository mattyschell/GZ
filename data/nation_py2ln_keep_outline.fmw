FME workspace nation_py2ln_keep_outline.fmw

Parameters:
- SourceDataset =
- SourceFileOnly =
- DestDataset =
- SumLev =
- Projection =
- LOG_FILE =
- ShapeName =

Readers:
- SHAPE_1: SHAPE from $(SourceDataset)

Writers:
- SHAPE_2: SHAPE to $(DestDataset)
- SHAPE_3: SHAPE to $(DestDataset)

geo_2013_p_00000_020_00_py_z9 (reader SHAPE_1)
    attributes: GEO_ID char(60), REGION char(1), NAME char(90), LSAD char(7)
    -> CoordinateRounder
CoordinateRounder
    ZPREC = 0
    YPREC = 6
    XPREC = 6
    ROUNDED -> Deaggregator
Deaggregator
    LIST_ATTR_MODE_LOOKUP = LEAN
    MODE = Flatten One Level
    SPLIT_COMPOSITES = No
    PART_NUMBER_FIELD = _part_number
    EXPLODE_INSTANCES = No
    GEOM_NAME_FIELD = _geometry_name
    DEAGGREGATED -> Dissolver
Dissolver
    GROUP_BY = fme_feature_type
    NO_OVRLP = No
    ACCUM_INPUT_ATTRS = No
    INTERIOR_LINE -> AttributeCreator
    AREA -> AttributeCreator
AttributeCreator
    ATTR_LIST = BDY_TYPE,$(SumLev),COVER_UNIT,U,COVER_ID,00
    -> Intersector
Intersector
    DUPLICATE_Z_NODES = No
    SEPARATE_COLLINEAR_SEGMENTS = No
    PERFORM_SELF_INTERSECTION = Yes
    SEG_ATTR = _segments
    OV_ATTR = _overlaps
    INTERSECTED -> LineJoiner
LineJoiner
    GROUP_BY = BDY_TYPE COVER_UNIT COVER_ID
    GROUP_BREAK = yes
    PRESERVE = no
    TOPOLOGY = End noded
    CONSIDER_NODE_ELEVATION = no
    BREAK = no
    LINE -> Reprojector
Reprojector
    DEST = $(Projection)
    RASTER_CELL_SIZE = Preserve Cells
    STROKE_ARCS = Yes
    INTERPOLATION_TYPE_NAME = Nearest Neighbor
    REPROJECTED -> AttributeKeeper
AttributeKeeper
    KEEP_ATTRS = BDY_TYPE,COVER_UNIT,COVER_ID
    -> GeometryValidator
GeometryValidator
    DUP_COORDS_CHECK_Z = Yes
    PRESETS = OGC
    ARC_ENDPOINT_TOLERANCE_MODE = Auto
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%""%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    REPAIR = No
    ISSUE_ATTR_NAME = _issues
    OGC_SIMPLE_CHECK = OGC_SIMPLE_CHECK
    PLANAR_TOLERANCE_MODE = Auto
    OGC_VALID_CHECK = OGC_VALID_CHECK
    PASSED -> $(ShapeName) (writer SHAPE_2)
    FAILED -> $(ShapeName)_FAILED (writer SHAPE_3)
$(ShapeName) (writer SHAPE_2)
    attributes: BDY_TYPE char(3), COVER_UNIT char(1), COVER_ID char(5)
$(ShapeName)_FAILED (writer SHAPE_3)
    attributes: BDY_TYPE char(3), COVER_UNIT char(1), COVER_ID char(5)

FME custom transformer LoopFilter_2
Tests whether a line is a loop, i.e. whether its end matches the beginning.
The transformers outputs loops through PASSED port, and non-loops through FAILED port.
The isLoop attribute added to each feature. 1 means the feature is loop, and zero means it is not.
Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)

FME custom transformer LoopFilter_3
Tests whether a line is a loop, i.e. whether its end matches the beginning.
The transformers outputs loops through PASSED port, and non-loops through FAILED port.
The isLoop attribute added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)

FME custom transformer AzimuthCalculator
Calculates the angle and the azimuth of a line or a polyline.
An Azimuth value can range from -180 to 180 With North as zero, South as -180, East as 90 and West as -90. 
Angles increase counterclockwise from the reference point of East (which represents zero degrees).
For polylines it returns the angle and azimuth of a line connecting the first and the last verteices of the polyline. 
The resultant lines have two new attributes - acAngle and acAzimuth.
For getting information about each segment of the polyline use PolylineAnalyzer.
This transformer uses an embedded version of " LoopFilter " custom transformer.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> GeometryFilter
Note: passes only lines to the next transfomer
GeometryFilter
    BREAK_AGG = No
    LINE -> LoopFilter
    POINT -> Not_Line (output)
    ARC -> Not_Line (output)
    AREA -> Not_Line (output)
    ELLIPSE -> Not_Line (output)
    TEXT -> Not_Line (output)
    RASTER -> Not_Line (output)
    POINTCLOUD -> Not_Line (output)
    SURFACE -> Not_Line (output)
    SOLID -> Not_Line (output)
    COLLECTION -> Not_Line (output)
    NULL -> Not_Line (output)
Note: tests whether a line is a loop
LoopFilter
    PASSED -> LOGGER_2
    FAILED -> COORDINATEFETCHER
LOGGER_2: Logger
    MESSAGE = Feature is a loop
    MAXFEATS = 20
    MAXCOORDS = 3
COORDINATEFETCHER: CoordinateFetcher
    Y_ATTR = acY1
    X_ATTR = acX1
    Z_DEFAULT = -9999
    Z_ATTR = acZ1
    IND = 0
    -> COORDINATEFETCHER_2
COORDINATEFETCHER_2: CoordinateFetcher
    Y_ATTR = acY2
    X_ATTR = acX2
    Z_DEFAULT = -9999
    Z_ATTR = acZ2
    IND = -1
    -> EXPRESSIONEVALUATOR_2
Note: EXPRESSIONEVALUATOR_2 [ExpressionEvaluator] / acAngle = acos((&acX2-&acX1)/sqrt(pow((&acY2-&acY1),2) + pow((&acX2-&acX1),2)))* (180/3.141592653589...
EXPRESSIONEVALUATOR_2: ExpressionEvaluator
    VAL_ATTR = acAngle
    EXPRESSION = acos((&acX2-&acX1)/sqrt(pow((&acY2-&acY1),2) + pow((&acX2-&acX1),2)))* (180/3.1415926535897932)
    -> EXPRESSIONEVALUATOR_6
EXPRESSIONEVALUATOR_6: ExpressionEvaluator
    VAL_ATTR = acAngle
    EXPRESSION = ((&acY2-&acY1)<0)?(360-&acAngle):(&acAngle)
    -> TESTER
Note: Azimuth Calculator / - Dean Hintz June 13 2005 / - Dmitri Bagh June 30 2005 (minor edits)
TESTER: Tester
    TEST_MODE = Automatic
    BOOL_OP = OR
    TEST_LIST = &acAngle,>,90
    TEST_CLAUSE = TEST &acAngle > 90
    PASSED -> TESTER_2
    FAILED -> EXPRESSIONEVALUATOR_3
TESTER_2: Tester
    TEST_MODE = Automatic
    BOOL_OP = OR
    TEST_LIST = &acAngle,""">""",270
    TEST_CLAUSE = TEST &acAngle ">" 270
    FAILED -> EXPRESSIONEVALUATOR_3
    PASSED -> EXPRESSIONEVALUATOR_5
EXPRESSIONEVALUATOR_5: ExpressionEvaluator
    VAL_ATTR = acAzimuth
    EXPRESSION = 450 - &acAngle
    -> ATTRIBUTEREMOVER
EXPRESSIONEVALUATOR_3: ExpressionEvaluator
    VAL_ATTR = acAzimuth
    EXPRESSION = 90 - &acAngle
    -> ATTRIBUTEREMOVER
Note: Removes all intermediate attributes
ATTRIBUTEREMOVER: AttributeRemover
    REMOVE_ATTRS = _isLoop,acX1,acY1,acZ1,acX2,acY2,acZ2
    -> AZIMUTH (output)
AZIMUTH (output)
Not_Line (output)

FME custom transformer VertexCounter
Replaces vertices in linear and area features with points and assigns to them numbers independently for each input feature. It also creates text labels for each point with its number. 
This transformer uses an embedded version of the "LoopFilter" custom transformer.
Label height is set to '1' by default, but it can be changed by the user. It is also possible to choose wheter or not to lable the last vertices in closed geometries (polygons and closed lines)
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- LABELPOINTREPLACER_HEIGHT = 1   # Label Height
- ATTRIBUTESETTER_VAL = 1   # Label Last Point in Loops (0 - yes/1 - no)

INPUT (input)
    -> GEOMETRYCOERCER
Note: Consider polygon as lines
GEOMETRYCOERCER: GeometryCoercer
    KIND = fme_line
    COERCED -> LoopFilter
LoopFilter
    PASSED -> COORDINATECOUNTER
    FAILED -> COORDINATECOUNTER
    NON-LINEAR -> COORDINATECOUNTER
Note: Counts Num of Coord in each feature
COORDINATECOUNTER: CoordinateCounter
    CNT_ATTR = vcCoordinateCounter
    -> COUNTER
Note: Counts the num of features for further aggreagating
COUNTER: Counter
    SCOPE = Global
    START = 0
    DOMAIN = LineID
    CNT_ATTR = vcLineID
    -> CHOPPER
Note: Makes points
CHOPPER: Chopper
    MAX = 1
    CHOPPED -> COUNTER_2
Note: Counts all points
COUNTER_2: Counter
    SCOPE = Global
    START = 0
    DOMAIN = VertexCounter
    CNT_ATTR = vcVertexCounter
    -> AGGREGATOR
    -> FEATUREMERGER [input 1]
Note: aggreagtes by initial feature id
AGGREGATOR: Aggregator
    GROUP_BY = vcLineID
    ACCUM_ATTRS = Yes
    LIST_NAME = vcMaxVertexID
    ORDERED = No
    AGGREGATE -> LISTRANGEEXTRACTOR
Note: Extracts the maximum Vertex Num in each feature
LISTRANGEEXTRACTOR: ListRangeExtractor
    SRC_LIST = vcMaxVertexID{}.vcVertexCounter
    MAX = _max
    MIN = _min
    -> FEATUREMERGER [input 2]
Note: Merges the max vertex num within feature / with each point made of this feature
FEATUREMERGER: FeatureMerger
    BUILD_INCOMPLETE = No
    PROCESS_DUPS = No
    MERGE_TYPE = Attributes Only
    REFERATTR = vcLineID
    REFEEATTR = vcLineID
    COMPLETE -> EXPRESSIONEVALUATOR
Note: EXPRESSIONEVALUATOR [ExpressionEvaluator] / _vertex_count = &vcVertexCounter+&vcCoordinateCounter-&_max
EXPRESSIONEVALUATOR: ExpressionEvaluator
    VAL_ATTR = _vertex_count
    EXPRESSION = &vcVertexCounter+&vcCoordinateCounter-&_max
    -> LISTREMOVER
LISTREMOVER: ListRemover
    LIST_ATTR = vcMaxVertexID{}
    -> ATTRIBUTEREMOVER_3
    -> ParameterFetcher
ATTRIBUTEREMOVER_3: AttributeRemover
    REMOVE_ATTRS = _isLoop,vcCoordinateCounter,_max,_min,fme_rotation,fme_text_size,fme_text_string,vcLineID,vcVertexCounter
    -> POINT (output)
POINT (output)
ParameterFetcher
    ATTR_LIST = LabelEndPoints {$(ATTRIBUTESETTER_VAL)}
    -> TESTER_3
TESTER_3: Tester
    TEST_MODE = Automatic
    TEST_DESCRIPTION = ""
    BOOL_OP = OR
    TEST_LIST = &LabelEndPoints,=,1
    TEST_CLAUSE = TEST "@Value(LabelEndPoints)" = "1"
    PASSED -> TESTER_2
    FAILED -> LABELPOINTREPLACER
Note: Testing whether a feature is loop
TESTER_2: Tester
    TEST_MODE = Automatic
    TEST_DESCRIPTION = ""
    BOOL_OP = OR
    TEST_LIST = &_isLoop,"""=""",0
    TEST_CLAUSE = TEST "@Value(_isLoop)" = "0"
    PASSED -> TESTER
    FAILED -> LABELPOINTREPLACER
Note: testing whether a vertex is the last in a feature
TESTER: Tester
    TEST_MODE = Automatic
    BOOL_OP = OR
    TEST_LIST = &_vertex_count,!=,&vcCoordinateCounter
    TEST_CLAUSE = TEST &_vertex_count != &vcCoordinateCounter
    PASSED -> LABELPOINTREPLACER
    FAILED -> ATTRIBUTEREMOVER_2
LABELPOINTREPLACER: LabelPointReplacer
    LABATTR = _vertex_count
    HEIGHT = $(LABELPOINTREPLACER_HEIGHT)
    LABELPOINT -> ATTRIBUTEREMOVER_2
ATTRIBUTEREMOVER_2: AttributeRemover
    REMOVE_ATTRS = _isLoop,_max,_min,LabelEndPoints,vcCoordinateCounter,vcLineID,vcVertexCounter
    -> LABEL (output)
LABEL (output)

Bookmark: Preparing lines and their vertices for further processing
  Attaching IDs, creating vertices, checking for loops
Note: assigns 0 to all loops, and 1 - to non-loops

FME custom transformer LoopFilter
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)

FME custom transformer LoopFilter_5
Tests whether a line is a loop, i.e. whether its end matches the beginning.
The transformers outputs loops through PASSED port, and non-loops through FAILED port.
An isLoop attribute is added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)

FME custom transformer PolylineAnalyzer
Takes polylines and polygons and analyzes relationships between their components - vertices and segments.
There are 9 outputs in the transformer:
- Starting Azimuth (direction of 0)
- Starting Angle (direction of 0)
- Vertex labels with their number within each line or area
- Vertices with their numbers, azimuths and angles of incoming and outgoing segments as attributes
- Segments of the original lines or areas with angle, azimuth, vertex numbers at the beginning and the end, and length as attributes.
- Angles between adjacent segments
- Angle of each segment
- Azimuth of each segment
- Invalid Inputs (non-linear and non-polygonal features) 
This transformer uses embedded versions of " LoopFilter ", " VertexCounter " and " AzimuthCalculator " custom transformers.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Note: Created By Dmitri Bagh / Summer 2005 / Updated January 2008 / Output ports in the transformer are ordered by their location from up to down
INPUT (input)
    -> GeometryFilter
GeometryFilter
    BREAK_AGG = No
    LINE -> COUNTER_3
    AREA -> GeometryCoercer
    POINT -> INVALID_INPUT (output)
    ARC -> INVALID_INPUT (output)
    ELLIPSE -> INVALID_INPUT (output)
    TEXT -> INVALID_INPUT (output)
    RASTER -> INVALID_INPUT (output)
    POINTCLOUD -> INVALID_INPUT (output)
    SURFACE -> INVALID_INPUT (output)
    SOLID -> INVALID_INPUT (output)
    COLLECTION -> INVALID_INPUT (output)
    NULL -> INVALID_INPUT (output)
Note: treating polygons as lines
GeometryCoercer
    KIND = fme_line
    COERCED -> COUNTER_3
Note: COUNTER_3 [Counter] / Count Attribute: acPolylineNum / Counter Name: PolylineNum / Count Start: 0
Note: Assigning PolylineID
COUNTER_3: Counter
    SCOPE = Global
    START = 0
    DOMAIN = PolylineNum
    CNT_ATTR = acPolylineNum
    -> COORDINATECOUNTER
Note: COORDINATECOUNTER [CoordinateCounter] / Coordinate Count Attribute: _coordcount
Note: Number of Coordinates per feature
COORDINATECOUNTER: CoordinateCounter
    CNT_ATTR = _coordcount
    -> LoopFilter
LoopFilter
    PASSED -> ATTRIBUTERENAMER_6
    FAILED -> ATTRIBUTERENAMER_6
ATTRIBUTERENAMER_6: AttributeRenamer
    ATTR_LIST = _PolylineLoop,_isLoop
    -> Chopper
    -> VertexCounter
VertexCounter
    ATTRIBUTESETTER_VAL = 1
    LABELPOINTREPLACER_HEIGHT = 1
    POINT -> COUNTER_2
    LABEL -> VERTEX_LABEL (output)
COUNTER_2: Counter
    SCOPE = Global
    START = 1
    DOMAIN = VertexNum
    CNT_ATTR = acVertexNum
    -> POINTONLINEOVERLAYER [input 1]
VERTEX_LABEL (output)
Chopper
    MAX = 2
    CHOPPED -> COUNTER
Note: Assinging unique / through dataset / Segment / Number
Note: COUNTER [Counter] / Count Attribute: acLineNum / Counter Name: LineNum / Count Start: 1
COUNTER: Counter
    SCOPE = Global
    START = 1
    DOMAIN = LineNum
    CNT_ATTR = acLineNum
    -> AzimuthCalculator
AzimuthCalculator
    AZIMUTH -> LENGTHCALCULATOR
LENGTHCALCULATOR: LengthCalculator
    LEN_ATTR = acLength
    MULT = 1
    DIM = 2
    -> POINTONLINEOVERLAYER [input 2]
POINTONLINEOVERLAYER: PointOnLineOverlayer
    LIST_NAME = AdjacentLines
    TOLERANCE = 0
    OV_ATTR = _overlaps
    LINE -> LISTINDEXER_3
    POINT -> MATCHER
Note: Deleting duplicates at the ends of loops
MATCHER: Matcher
    MATCH = 3D
    BLANK_AND_MISSING_DIFFER = No
    CNT_ATTR = _match_id
    NOT_MATCHED -> LISTELEMENTCOUNTER
    SINGLE_MATCHED -> LISTELEMENTCOUNTER
LISTELEMENTCOUNTER: ListElementCounter
    LIST_NAME = AdjacentLines{}
    CNT_ATTR = _element_count
    -> LISTSORTER
LISTSORTER: ListSorter
    TYPE = Numeric
    SRC_LIST = AdjacentLines{}.acLineNum
    ORDER = Increasing
    -> TESTER_2
Note: Separate the first vertex from others
TESTER_2: Tester
    TEST_MODE = Automatic
    BOOL_OP = AND
    TEST_LIST = &_vertex_count,=,1
    TEST_CLAUSE = TEST @Value(_vertex_count) = 1
    FAILED -> LISTINDEXER
    PASSED -> TESTER_4
Note: Sepatate Loops from non-loops
TESTER_4: Tester
    TEST_MODE = Automatic
    BOOL_OP = AND
    TEST_LIST = &_PolylineLoop,=,0
    TEST_CLAUSE = TEST @Value(_PolylineLoop) = 0
    FAILED -> ATTRIBUTERENAMER_2
    PASSED -> LISTINDEXER_5
LISTINDEXER_5: ListIndexer
    LIST_ATTR = AdjacentLines{}
    INDEX = 0
    -> ATTRIBUTERENAMER_7
ATTRIBUTERENAMER_7: AttributeRenamer
    ATTR_LIST = acAngleOut,acAngle,acAzimuthOut,acAzimuth
    -> LISTINDEXER_6
LISTINDEXER_6: ListIndexer
    LIST_ATTR = AdjacentLines{}
    INDEX = 1
    -> ATTRIBUTERENAMER_5
ATTRIBUTERENAMER_5: AttributeRenamer
    ATTR_LIST = acAngleIn,acAngle,acAzimuthIn,acAzimuth
    -> EXPRESSIONEVALUATOR_3
LISTINDEXER: ListIndexer
    LIST_ATTR = AdjacentLines{}
    INDEX = 0
    -> ATTRIBUTERENAMER
ATTRIBUTERENAMER: AttributeRenamer
    ATTR_LIST = acAngleIn,acAngle,acAzimuthIn,acAzimuth
    -> LISTINDEXER_2
LISTINDEXER_2: ListIndexer
    LIST_ATTR = AdjacentLines{}
    INDEX = 1
    -> ATTRIBUTERENAMER_2
ATTRIBUTERENAMER_2: AttributeRenamer
    ATTR_LIST = acAngleOut,acAngle,acAzimuthOut,acAzimuth
    -> EXPRESSIONEVALUATOR_3
Note: Changing incoming azimuth by 180 degrees
EXPRESSIONEVALUATOR_3: ExpressionEvaluator
    VAL_ATTR = acAzimuthIn
    EXPRESSION = &acAzimuthIn-180
    -> LISTREMOVER
Note: No need in list anymore
LISTREMOVER: ListRemover
    LIST_ATTR = AdjacentLines{}
    -> GeometryCoercer_2
Note: 2008 edits / ListIndexers could turn points into lines
GeometryCoercer_2
    KIND = fme_point
    COERCED -> TESTER
Note: if vertex has two adjacent segments, / calculate an angle between them
TESTER: Tester
    TEST_MODE = Automatic
    BOOL_OP = AND
    TEST_LIST = &_element_count,=,2
    TEST_CLAUSE = TEST &_element_count = 2
    PASSED -> EXPRESSIONEVALUATOR
    FAILED -> COORDINATEFETCHER
Note: EXPRESSIONEVALUATOR [ExpressionEvaluator] / AngleBetweenLines = ((&acAzimuthIn-&acAzimuthOut)<0)?(&acAzimuthIn-&acAzimuthOut+360):(&acAzimuthIn-...
Note: Calculating Angle between segments / AzIn - AzOut (+360)
EXPRESSIONEVALUATOR: ExpressionEvaluator
    VAL_ATTR = AngleBetweenLines
    EXPRESSION = ((&acAzimuthIn-&acAzimuthOut)<0)?(&acAzimuthIn-&acAzimuthOut+360):(&acAzimuthIn-&acAzimuthOut)
    -> EXPRESSIONEVALUATOR_4
Note: If angle still negative adjust by adding 360 degrees
EXPRESSIONEVALUATOR_4: ExpressionEvaluator
    VAL_ATTR = AngleBetweenLines
    EXPRESSION = (&AngleBetweenLines<0)?(&AngleBetweenLines+360):(&AngleBetweenLines)
    -> COORDINATEFETCHER
Note: Extract coordinates for zero angle building
COORDINATEFETCHER: CoordinateFetcher
    Y_ATTR = acY
    X_ATTR = acX
    Z_DEFAULT = -9999
    Z_ATTR = acZ
    IND = 0
    -> ATTRIBUTEREMOVER
    -> TESTER_3
TESTER_3: Tester
    TEST_MODE = Automatic
    BOOL_OP = OR
    TEST_LIST = &acAngleOut,!=,
    TEST_CLAUSE = TEST &acAngleOut != ""
    PASSED -> EXPRESSIONEVALUATOR_5
    PASSED -> POINTCONNECTOR_2
    PASSED -> POINTCONNECTOR
    PASSED -> EXPRESSIONEVALUATOR_2
    PASSED -> 2DARCREPLACER_3
    PASSED -> 2DARCREPLACER
    PASSED -> TESTER_6
EXPRESSIONEVALUATOR_5: ExpressionEvaluator
    VAL_ATTR = d_acY
    EXPRESSION = &acY+3
    -> 2DPOINTREPLACER_3
2DPOINTREPLACER_3: 2DPointReplacer
    XVALATTR = @Value(acX)
    YVALATTR = @Value(d_acY)
    POINT -> POINTCONNECTOR_2
POINTCONNECTOR_2: PointConnector
    BREAKATTR = acVertexNum
    LINE -> ATTRIBUTEREMOVER_7
ATTRIBUTEREMOVER_7: AttributeRemover
    REMOVE_ATTRS = _coordcount,_element_count,_isLoop,_match_id,_overlaps,_PolylineLoop,acAngleIn,acAngleOut,acAzimuthIn,acAzimuthOut,acLength,acLineNum,acPolylineNum,acVertexNum,acX,acY,acZ,AngleBetweenLines,d_acY
    -> AZIMUTH_START (output)
AZIMUTH_START (output)
EXPRESSIONEVALUATOR_2: ExpressionEvaluator
    VAL_ATTR = d_acX
    EXPRESSION = &acX+3
    -> 2DPOINTREPLACER_2
2DPOINTREPLACER_2: 2DPointReplacer
    XVALATTR = @Value(d_acX)
    YVALATTR = @Value(acY)
    POINT -> POINTCONNECTOR
POINTCONNECTOR: PointConnector
    BREAKATTR = acVertexNum
    LINE -> ATTRIBUTEREMOVER_2
ATTRIBUTEREMOVER_2: AttributeRemover
    REMOVE_ATTRS = _coordcount,_element_count,_isLoop,_match_id,_overlaps,_PolylineLoop,acAngleIn,acAngleOut,acAzimuthIn,acAzimuthOut,acLength,acLineNum,acPolylineNum,acX,acY,acZ,AngleBetweenLines,d_acX,acVertexNum
    -> ANGLE_START (output)
ANGLE_START (output)
Note: Added in January 2008 for the first vertex of non-loops
TESTER_6: Tester
    TEST_MODE = Automatic
    BOOL_OP = OR
    TEST_LIST = &acAngleIn,!=,
    TEST_CLAUSE = TEST @Value(acAngleIn) != ""
    PASSED -> 2DARCREPLACER_2
2DARCREPLACER_2: 2DArcReplacer
    XVALATTR = @Value(acX)
    SWEEPANG = @Value(AngleBetweenLines)
    PRIMAXIS = 2.5
    YVALATTR = @Value(acY)
    SECAXIS = 2.5
    ROT = 180
    STARTANG = @Value(acAngleIn)
    ARC -> ATTRIBUTEREMOVER_4
ATTRIBUTEREMOVER_4: AttributeRemover
    REMOVE_ATTRS = _element_count,_overlaps,acAngleIn,acAngleOut,acX,acY,acZ,_coordcount,_isLoop,_match_id,_PolylineLoop,acAzimuthIn,acAzimuthOut,acLength,acLineNum,acPolylineNum,acVertexNum
    -> ANGLE (output)
ANGLE (output)
2DARCREPLACER: 2DArcReplacer
    XVALATTR = @Value(acX)
    SWEEPANG = @Value(acAngleOut)
    PRIMAXIS = 2
    YVALATTR = @Value(acY)
    SECAXIS = 2
    ROT = 0
    STARTANG = 0
    ARC -> ATTRIBUTEREMOVER_3
ATTRIBUTEREMOVER_3: AttributeRemover
    REMOVE_ATTRS = _element_count,_overlaps,acAngleIn,acAzimuthIn,acAzimuthOut,acX,acY,acZ,AngleBetweenLines,_coordcount,_isLoop,_match_id,_PolylineLoop,acLength,acLineNum,acPolylineNum,acVertexNum
    -> SEGMENT_ANGLE (output)
SEGMENT_ANGLE (output)
2DARCREPLACER_3: 2DArcReplacer
    XVALATTR = @Value(acX)
    SWEEPANG = @Value(acAzimuthOut)
    PRIMAXIS = 1.5
    YVALATTR = @Value(acY)
    SECAXIS = 1.5
    ROT = @Value(acAngleOut)
    STARTANG = 0
    ARC -> ATTRIBUTEREMOVER_6
ATTRIBUTEREMOVER_6: AttributeRemover
    REMOVE_ATTRS = _coordcount,_element_count,_isLoop,_match_id,_overlaps,_PolylineLoop,acAngleIn,acAzimuthIn,acLength,acLineNum,acPolylineNum,acVertexNum,acX,acY,acZ,AngleBetweenLines,acAngleOut
    -> SEGMENT_AZIMUTH (output)
SEGMENT_AZIMUTH (output)
ATTRIBUTEREMOVER: AttributeRemover
    REMOVE_ATTRS = _element_count,_overlaps,acX,acY,acZ,_coordcount,_isLoop,_match_id,_PolylineLoop,acLength,acLineNum,acPolylineNum
    -> VERTEX (output)
VERTEX (output)
LISTINDEXER_3: ListIndexer
    LIST_ATTR = AdjacentLines{}
    INDEX = 0
    -> ATTRIBUTERENAMER_3
ATTRIBUTERENAMER_3: AttributeRenamer
    ATTR_LIST = acVertexNumBeg,_vertex_count
    -> LISTINDEXER_4
LISTINDEXER_4: ListIndexer
    LIST_ATTR = AdjacentLines{}
    INDEX = 1
    -> ATTRIBUTERENAMER_4
ATTRIBUTERENAMER_4: AttributeRenamer
    ATTR_LIST = acVertexNumEnd,_vertex_count
    -> LISTREMOVER_2
LISTREMOVER_2: ListRemover
    LIST_ATTR = AdjacentLines{}
    -> ATTRIBUTEREMOVER_5
ATTRIBUTEREMOVER_5: AttributeRemover
    REMOVE_ATTRS = _coordcount,_isLoop,_overlaps,acPolylineNum,acVertexNum,_PolylineLoop
    -> SEGMENT (output)
SEGMENT (output)
Note: Dragging this up may cause the output port to be / shown in the middle of the other ports (instead of last)
INVALID_INPUT (output)

Bookmark: Extracting incoming and outcoming angles and azimuthes from non-first vertex list in loops and all vertices in non-loops
Note: No need in incoming angle and azimuth for the first vertex of non-loops

FME custom transformer LoopFilter_4
Tests whether a line is a loop, i.e. whether its end matches the beginning.
The transformers outputs loops through PASSED port, and non-loops through FAILED port.
The isLoop attribute added to each feature. 1 means the feature is loop, and zero means it is not.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

LINE (input)
    -> LineFilter
Note: LoopFilter / Dmitri Bagh / July 11, 2005
LineFilter: GeometryFilter
    LINE -> LoopTester
    POINT -> NON-LINEAR (output)
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: / TEST &_isLoop = 0 / Condition: OR / Composite Test Expression:
TESTER: Tester
    TEST_MODE = Automatic
    BOOL_OP = OR
    TEST_LIST = &_isLoop,=,0
    TEST_CLAUSE = TEST &_isLoop = 0
    PASSED -> PASSED (output)
    FAILED -> FAILED (output)
PASSED (output)
FAILED (output)
NON-LINEAR (output)
