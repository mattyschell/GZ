FME workspace state_edges_tables_to_nation_polygons.fmw

Parameters:
- SourceDataset_ORACLE8I = EDEVBNCH.GEO.CENSUS.GOV   # Source Oracle Spatial Object Service
- FEATURE_TYPES = DADSGEN.STATE_EDGES_Z6
- DestDataset_SHAPE = Q:\gz\dev\devbnch\mcard001\qa_20120918   # Destination ESRI Shape Directory

Readers:
- ORACLE8I_1: ORACLE8I from $(SourceDataset_ORACLE8I)

Writers:
- SHAPE_1: SHAPE to $(DestDataset_SHAPE)

STATE_EDGES_Z6_LINE (reader ORACLE8I_1)
    attributes: SRC varchar2(8), TYPE varchar2(32), L_STATEFP varchar2(32), R_STATEFP varchar2(32), STEDGE_ID float
    -> PolygonBuilder
PolygonBuilder
    ALLOW_CYCLES = No
    POLYGON -> AttributeCreator
AttributeCreator
    ATTR_LIST = STATEFP,99
    -> Dissolver
Dissolver
    DISSOLVE_MODE = Traditional
    ACCUM_INPUT_ATTRS = No
    GROUP_BY = STATEFP
    OVRLP = Overlap
    AREA -> Reprojector
Reprojector
    DEST = SPHERICAL_MERCATOR
    SOURCE = Read from feature
    RASTER_CELL_SIZE = Preserve Cells
    INTERPOLATION_TYPE_NAME = Nearest Neighbor
    STROKE_ARCS = Yes
    REPROJECTED -> shoreline_z6 (writer SHAPE_1)
shoreline_z6 (writer SHAPE_1)
Inspector
